<![CDATA[
module ietf-bfd-opt-auth {
  yang-version 1.1;
  namespace "urn:ietf:params:xml:ns:yang:ietf-bfd-opt-auth";
  prefix bfd-oa;

  import ietf-routing {
    prefix rt;
    reference
      "RFC 8349: A YANG Data Model for Routing Management
       (NMDA version).";
  }

  import ietf-bfd {
    prefix bfd;
    reference
      "RFC 9314: YANG Data Model for Bidirectional
       Forwarding Detection (BFD).";
  }

  import ietf-bfd-ip-sh {
    prefix bfd-ip-sh;
    reference
      "RFC 9314: YANG Data Model for Bidirectional
       Forwarding Detection (BFD).";
  }

  import ietf-bfd-ip-mh {
    prefix bfd-ip-mh;
    reference
      "RFC 9314: YANG Data Model for Bidirectional
       Forwarding Detection (BFD).";
  }

  import ietf-bfd-lag {
    prefix bfd-lag;
    reference
      "RFC 9314: YANG Data Model for Bidirectional
       Forwarding Detection (BFD).";
  }

  import ietf-bfd-mpls {
    prefix bfd-mpls;
    reference
      "RFC 9314: YANG Data Model for Bidirectional
       Forwarding Detection (BFD).";
  }

  organization
    "IETF Bidirectional Forwarding Detection (BFD) Working Group";

  contact
    "WG Web:   <http://tools.ietf.org/wg/bfd>
     WG List:  <rtg-bfd@ietf.org>

     Authors: Mahesh Jethanandani (mjethanandani@gmail.com)
              Ashesh Mishra (ashesh@aalyria.com)
              Ankur Saxena (ankurpsaxena@gmail.com)
              Manav Bhatia (mnvbhatia@google.com)
              Jeffrey Haas (jeffrey.haas@hpe.com).";
              
  description
    "This YANG module augments the base BFD YANG module to add
     attributes related to the experimental BFD Optimized
     Authentication.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9985
     (https://www.rfc-editor.org/info/rfc9985); see the RFC itself
     for full legal notices.";

  revision "2026-06-19" {
    description
      "Initial Version.";
    reference
      "RFC 9985: Optimizing BFD Authentication.";
  }

  feature optimized-auth {
    description
      "Indicates that the implementation supports optimized
       authentication.";
    reference
      "RFC 9985: Optimizing BFD Authentication.";
  }

  grouping bfd-opt-auth-config {
    description
      "Grouping for BFD Optimized Authentication Parameters.";
    leaf reauth-interval {
      type uint32;
      units "seconds";
      default "60";
      description
        "Interval of time after which more computationally intensive
         authentication should be utilized to prevent an
         on-path-attacker attack.

         A value of zero means that we do not do periodic
         reauthentication using the more computationally intensive
         authentication method.

         This value SHOULD have jitter applied to it to avoid
         self-synchronization during expensive authentication
         operations.";
    }
  }

  augment "/rt:routing/rt:control-plane-protocols" 
        + "/rt:control-plane-protocol/bfd:bfd/bfd-ip-sh:ip-sh" 
        + "/bfd-ip-sh:sessions/bfd-ip-sh:session" 
        + "/bfd-ip-sh:authentication" {
    uses bfd-opt-auth-config;

    description
      "Augment the 'authentication' container for single-hop BFD
       module to add attributes related to BFD Optimized
       Authentication.";
  }

  augment "/rt:routing/rt:control-plane-protocols" 
        + "/rt:control-plane-protocol/bfd:bfd/bfd-ip-mh:ip-mh" 
        + "/bfd-ip-mh:session-groups/bfd-ip-mh:session-group" 
        + "/bfd-ip-mh:authentication" {
    uses bfd-opt-auth-config;

    description
      "Augment the 'authentication' container for multi-hop BFD
       module to add attributes related to BFD Optimized
       Authentication.";
  }

  augment "/rt:routing/rt:control-plane-protocols" 
        + "/rt:control-plane-protocol/bfd:bfd/bfd-lag:lag" 
        + "/bfd-lag:sessions/bfd-lag:session" 
        + "/bfd-lag:authentication" {
    uses bfd-opt-auth-config;

    description
      "Augment the 'authentication' container for BFD over LAG
       module to add attributes related to BFD Optimized
       Authentication.";
  }

  augment "/rt:routing/rt:control-plane-protocols" 
        + "/rt:control-plane-protocol/bfd:bfd/bfd-mpls:mpls" 
        + "/bfd-mpls:session-groups/bfd-mpls:session-group" 
        + "/bfd-mpls:authentication" {
    uses bfd-opt-auth-config;

    description
      "Augment the 'authentication' container for BFD over MPLS
       module to add attributes related to BFD Optimized
       Authentication.";
  }
}]]>
